FME workspace maidenhead_to_pg.fmw

Parameters:
- SourceDataset_ESRISHAPE = X:\Common_Data\Shapefiles\maidenhead_grids\**\*.shp   # Source Esri Shapefile(s)
- FEATURE_TYPES =

Readers:
- ESRISHAPE_1: ESRISHAPE from $(SourceDataset_ESRISHAPE)

Bookmark: Spatial WSPR Data
AA00 (reader ESRISHAPE_1)
    attributes: GridSquare char(8)
    -> Reprojector
Reprojector
    DEST = EPSG:4326
    INTERPOLATION_TYPE_NAME = Nearest Neighbor
    RASTER_CELL_SIZE = Preserve Cells
    RASTER_TOLERANCE = 0.0
    SOURCE = Read from feature
    REPROJECTED -> AttributeCreator
AttributeCreator
    ATTR_TABLE = SET_TO grid = @Value(fme_feature_type)
    -> StringConcatenator

Bookmark: Write to PG
StringConcatenator
    ACTION = Create New Attribute
    PARM_LINE = @Value(fme_feature_type)@Value(GridSquare)
    VAL_ATTR = subgrid
    -> StringCaseChanger
StringCaseChanger
    ATTRCHOICE = Selected Attributes
    ATTRLIST = GridSquare subgrid grid fme_feature_type
    CHANGE_TYPE = lowercase
    -> FeatureWriter [Table1]
FeatureWriter
    DATASET = Ross
    DATASET_ATTR = _dataset
    FEATURE_TYPE_LIST_ATTR = _feature_type
    FORMAT = POSTGIS
    POSTGIS_BULK_COPY = YES
    POSTGIS_COORDINATE_SYSTEM_GRANULARITY = FEATURE_TYPE
    POSTGIS_GENERIC_GEOMETRY = no
    POSTGIS_INSERT_TEXT_GEOMETRY = NO
    POSTGIS_LOWERCASE_ATTRIBUTE_NAMES = Yes
    POSTGIS_NAMED_CONNECTION = Ross
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> FeatureWriter_Summary
FeatureWriter_Summary: Logger
    LOG_FEATURE = LOG_ONLY
    MAXCOORDS = 20
    MAXFEATS = 20
    MESSAGE = Feature is:
    SEVERITY = INFO
